-- Depth stress fixture used by the vest_asn1 scalability experiments.
-- Both chains have one nested component per definition.
Depth18 DEFINITIONS EXPLICIT TAGS ::= BEGIN
    Seq0 ::= BOOLEAN
    Choice0 ::= BOOLEAN

    Seq1 ::= SEQUENCE { value Seq0 }
    Choice1 ::= CHOICE { value [1] EXPLICIT Choice0 }
    Seq2 ::= SEQUENCE { value Seq1 }
    Choice2 ::= CHOICE { value [2] EXPLICIT Choice1 }
    Seq3 ::= SEQUENCE { value Seq2 }
    Choice3 ::= CHOICE { value [3] EXPLICIT Choice2 }
    Seq4 ::= SEQUENCE { value Seq3 }
    Choice4 ::= CHOICE { value [4] EXPLICIT Choice3 }
    Seq5 ::= SEQUENCE { value Seq4 }
    Choice5 ::= CHOICE { value [5] EXPLICIT Choice4 }
    Seq6 ::= SEQUENCE { value Seq5 }
    Choice6 ::= CHOICE { value [6] EXPLICIT Choice5 }
    Seq7 ::= SEQUENCE { value Seq6 }
    Choice7 ::= CHOICE { value [7] EXPLICIT Choice6 }
    Seq8 ::= SEQUENCE { value Seq7 }
    Choice8 ::= CHOICE { value [8] EXPLICIT Choice7 }
    Seq9 ::= SEQUENCE { value Seq8 }
    Choice9 ::= CHOICE { value [9] EXPLICIT Choice8 }
    Seq10 ::= SEQUENCE { value Seq9 }
    Choice10 ::= CHOICE { value [10] EXPLICIT Choice9 }
    Seq11 ::= SEQUENCE { value Seq10 }
    Choice11 ::= CHOICE { value [11] EXPLICIT Choice10 }
    Seq12 ::= SEQUENCE { value Seq11 }
    Choice12 ::= CHOICE { value [12] EXPLICIT Choice11 }
    Seq13 ::= SEQUENCE { value Seq12 }
    Choice13 ::= CHOICE { value [13] EXPLICIT Choice12 }
    Seq14 ::= SEQUENCE { value Seq13 }
    Choice14 ::= CHOICE { value [14] EXPLICIT Choice13 }
    Seq15 ::= SEQUENCE { value Seq14 }
    Choice15 ::= CHOICE { value [15] EXPLICIT Choice14 }
    Seq16 ::= SEQUENCE { value Seq15 }
    Choice16 ::= CHOICE { value [16] EXPLICIT Choice15 }
    Seq17 ::= SEQUENCE { value Seq16 }
    Choice17 ::= CHOICE { value [17] EXPLICIT Choice16 }
    Seq18 ::= SEQUENCE { value Seq17 }
    Choice18 ::= CHOICE { value [18] EXPLICIT Choice17 }
END
