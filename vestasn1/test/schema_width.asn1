-- Width stress fixture used by the vestasn1 scalability experiments.
-- Fields cycle through OPTIONAL, DEFAULT, and required components.
SequenceWidth16 DEFINITIONS EXPLICIT TAGS ::= BEGIN
    AutomationSequence ::= SEQUENCE {
        field0 [0] IMPLICIT BOOLEAN OPTIONAL,
        field1 [1] IMPLICIT BOOLEAN DEFAULT FALSE,
        field2 [2] IMPLICIT BOOLEAN,
        field3 [3] IMPLICIT BOOLEAN OPTIONAL,
        field4 [4] IMPLICIT BOOLEAN DEFAULT FALSE,
        field5 [5] IMPLICIT BOOLEAN,
        field6 [6] IMPLICIT BOOLEAN OPTIONAL,
        field7 [7] IMPLICIT BOOLEAN DEFAULT FALSE,
        field8 [8] IMPLICIT BOOLEAN,
        field9 [9] IMPLICIT BOOLEAN OPTIONAL,
        field10 [10] IMPLICIT BOOLEAN DEFAULT FALSE,
        field11 [11] IMPLICIT BOOLEAN,
        field12 [12] IMPLICIT BOOLEAN OPTIONAL,
        field13 [13] IMPLICIT BOOLEAN DEFAULT FALSE,
        field14 [14] IMPLICIT BOOLEAN,
        field15 [15] IMPLICIT BOOLEAN OPTIONAL
    }
END
