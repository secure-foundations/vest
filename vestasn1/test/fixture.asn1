Fixture DEFINITIONS EXPLICIT TAGS ::= BEGIN
    Flag ::= BOOLEAN
    Count ::= INTEGER
    TaggedCount ::= [4] IMPLICIT Count
    RetaggedCount ::= [5] IMPLICIT TaggedCount
    Payload ::= OCTET STRING (SIZE (2..4))

    Header ::= SEQUENCE {
        flag Flag,
        count Count
    }

    Envelope ::= SEQUENCE {
        header Header,
        payload [0] IMPLICIT Payload OPTIONAL
    }

    Envelopes ::= SEQUENCE OF Envelope

    Features ::= SEQUENCE {
        enabled [0] IMPLICIT Flag DEFAULT TRUE,
        visible [1] IMPLICIT BOOLEAN DEFAULT FALSE
    }

    Selection ::= CHOICE {
        flag [1] IMPLICIT Flag,
        payload [2] EXPLICIT Payload
    }

    ChoiceEnvelope ::= SEQUENCE {
        selection [3] IMPLICIT Selection OPTIONAL
    }

    Color ::= ENUMERATED {
        red(0),
        green(1),
        blue(2)
    }

    Identifier ::= OBJECT IDENTIFIER
    Measurement ::= REAL
    OpenValue ::= ANY
    BmpName ::= BMPString (SIZE (1..4))

    BmpContainer ::= SEQUENCE {
        name BmpName
    }

    Metadata ::= SEQUENCE {
        color [0] IMPLICIT Color DEFAULT green,
        identifier Identifier,
        measurement Measurement,
        open [1] EXPLICIT OpenValue
    }

    InlineRecord ::= SEQUENCE {
        nested SEQUENCE {
            payload OCTET STRING
        },
        selected CHOICE {
            flag [2] IMPLICIT BOOLEAN,
            identifier [3] IMPLICIT OBJECT IDENTIFIER
        }
    }

    AutomationChoice ::= CHOICE {
        booleanValue [10] IMPLICIT BOOLEAN,
        integerValue [11] IMPLICIT INTEGER,
        octetsValue [12] IMPLICIT OCTET STRING,
        nullValue [13] IMPLICIT NULL,
        textValue [14] EXPLICIT UTF8String,
        oidValue [15] EXPLICIT OBJECT IDENTIFIER
    }

    AutomationSequence ::= SEQUENCE {
        prefix [20] IMPLICIT BOOLEAN OPTIONAL,
        enabled [21] IMPLICIT BOOLEAN DEFAULT TRUE,
        payload [22] EXPLICIT OCTET STRING OPTIONAL,
        marker [23] IMPLICIT NULL,
        selected [24] EXPLICIT AutomationChoice OPTIONAL
    }

    featureEnabled Flag ::= TRUE
    answer Count ::= 42
    defaultColor Color ::= green
END
